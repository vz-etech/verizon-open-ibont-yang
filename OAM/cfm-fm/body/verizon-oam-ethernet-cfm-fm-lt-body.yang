submodule verizon-oam-ethernet-cfm-fm-lt-body {
  belongs-to verizon-oam-ethernet-cfm-fm {
    prefix vz-oam-ecfm-fm;
  }

  import ietf-yang-types {
    prefix yang;
  }

  organization
    "Verizon";

  contact
    "Comments or questions about this Verizon YANG module should be
     directed to <mailto:vz-open-netconf-yang@verizon.com>";

  description
    "This module contains a collection YANG data types and
     grouping definitions that extend the functionality of 
     Connectivity Fault Management (CFM) as specified in 
     IEEE 802.1ag with additional functionality to support 
     the Ethernet Linktrace (ETH-LT) function of Ethernet Service 
     Layer OAM Fault Management as specified by ITU-T Y.1731 
     clause 7.3.

     Note that MEG, MEG ID and MEG level in ITU-T Y.1731 align with 
     MA, MAID and MA level respectively in IEEE 802.1ag.

     Copyright (c) 2019, Verizon and Calix.   All rights reserved.";

  revision "2020-10-04" {
    description
      "Initial revision";
    reference 
      "ITU-T Y.1731-2015 clause 7.3; MEF 7.2 clause 7.5.";
  }


  feature eth-lt {
    description
      "Indicates support for the Ethernet Link Trace (ETH-LT)
       protocol acc. to ITU-T Y.1731.";
  }


  grouping eth-lt-statistics-parameters {
    description
      "Statistics parameters for the linktrace protocol of a MEP.";
    reference
      "MEF 7.2 clause 7.5.3.2 (EthOamLtrStats).";

    leaf out-ltm {
      type yang:counter64;
      description
        "The total number of LTMs transmitted by the MEP.";
      reference
        "MEF 7.2 clause 7.5.3.2 (ltmTransmitted).";
    }
    leaf in-ltm {
      type yang:counter64;
      description
        "The total number of LTMs received by the MEP.";
      reference
        "MEF 7.2 clause 7.5.3.2 (ltmReceived).";
    }
    leaf out-ltr {
      type yang:counter64;
      description
        "The total number of LTRs transmitted by the MEP.";
      reference
        "MEF 7.2 clause 7.5.3.2 (ltrTransmitted).";
    }
    leaf in-ltr {
      type yang:counter64;
      description
        "The total number of LTRs received by the MEP.";
      reference
        "MEF 7.2 clause 7.5.3.2 (ltrReceived).";
    }
  }
}
