submodule verizon-oam-ethernet-cfm-fm-cc {
  belongs-to verizon-oam-ethernet-cfm-fm {
    prefix vz-oam-ecfm-fm;
  }

  import verizon-oam-ethernet-cfm {
    prefix vz-oam-ecfm;
  }

  include verizon-oam-ethernet-cfm-fm-cc-body;

  organization
    "Verizon";

  contact
    "Comments or questions about this Verizon YANG module should be
     directed to <mailto:vz-open-netconf-yang@verizon.com>";

  description
    "This module contains a collection of YANG definitions that 
     extend the functionality of Connectivity Fault Management 
     (CFM) as specified in IEEE 802.1ag with additional 
     functionality to support the Ethernet Continuity Check (ETH-CC) 
     function of Ethernet Service Layer OAM Fault Management as 
     specified by ITU-T Y.1731 clause 7.1.

     Note that MEG, MEG ID and MEG level in ITU-T Y.1731 align with 
     MA, MAID and MA level respectively in IEEE 802.1ag.

     Copyright (c) 2019, Verizon and Calix.   All rights reserved.";

  revision "2020-10-04" {
    description
      "Initial revision";
    reference 
      "ITU-T Y.1731-2015 clause 7.1; MEF 7.2 clause 7.5.";
  }


  /* Augment MEP continuity check configuration ETH-CC specific 
   *  nodes. 
   */
  augment "/vz-oam-ecfm:cfm/vz-oam-ecfm:domains/vz-oam-ecfm:domain"
        + "/vz-oam-ecfm:associations/vz-oam-ecfm:association"
        + "/vz-oam-ecfm:meps/vz-oam-ecfm:mep"
        + "/vz-oam-ecfm:continuity-check" {
    description
      "Add configuration nodes to continuity check to support 
       the ETH-CC function.";

    uses eth-cc-config-parameters;
  }

  /* Augment MEP continuity check operational status ETH-CC specific 
   *  nodes. 
   */
  augment "/vz-oam-ecfm:cfm-state/vz-oam-ecfm:domains"
        + "/vz-oam-ecfm:domain/vz-oam-ecfm:associations"
        + "/vz-oam-ecfm:association/vz-oam-ecfm:meps/vz-oam-ecfm:mep"
        + "/vz-oam-ecfm:continuity-check" {
    description
      "Add operational status nodes to continuity check to support 
       the ETH-CC function.";

    uses eth-cc-status-parameters;
  }

  augment "/vz-oam-ecfm:cfm-state/vz-oam-ecfm:domains"
        + "/vz-oam-ecfm:domain/vz-oam-ecfm:associations"
        + "/vz-oam-ecfm:association/vz-oam-ecfm:meps/vz-oam-ecfm:mep"
        + "/vz-oam-ecfm:statistics/vz-oam-ecfm:continuity-check" {
    description
      "Add additional statistics for the ETH-CC function.

           Editor's note: 
           Currently two solutions for implementing statistics 
           within this model are included as the discussion of 
           which solution to choose is ongoing:
           1 - collect all statistics for a MEP at the MEP level
               (this solution); 
           2 - collect statistics per CFM protocol.";

    uses eth-cc-statistics-parameters;
  }

  augment "/vz-oam-ecfm:cfm-state/vz-oam-ecfm:domains"
        + "/vz-oam-ecfm:domain/vz-oam-ecfm:associations"
        + "/vz-oam-ecfm:association/vz-oam-ecfm:meps"
        + "/vz-oam-ecfm:mep/vz-oam-ecfm:continuity-check"
        + "/vz-oam-ecfm:statistics" {
    description
      "Add additional statistics for the ETH-CC function.

           Editor's note: 
           Currently two solutions for implementing statistics 
           within this model are included as the discussion of 
           which solution to choose is ongoing:
           1 - collect all statistics for a MEP at the MEP level; 
           2 - collect statistics per CFM protocol.
               (this solution).";

    uses eth-cc-statistics-parameters;
  }
}
