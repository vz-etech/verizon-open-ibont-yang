submodule verizon-oam-ethernet-cfm-fm-ma {
  belongs-to verizon-oam-ethernet-cfm-fm {
    prefix vz-oam-ecfm-fm;
  }

  import verizon-oam-ethernet-cfm {
    prefix vz-oam-ecfm;
  }

  organization
    "Verizon";

  contact
    "Comments or questions about this Verizon YANG module should be
     directed to <mailto:vz-open-netconf-yang@verizon.com>";

  description
    "This module contains a collection of YANG definitions for the 
     management of Maintenance Associations (MA) that 
     extend the functionality within the within Connectivity 
     Management (CFM) as specified in IEEE 802.1ag with additional 
     functionality for Ethernet Service Layer OAM Fault Management 
     as specified by ITU-T Y.1731.

     Note that MEG, MEG ID and MEG level in ITU-T Y.1731 align with 
     MA, MAID and MA level respectively in IEEE 802.1ag.

     Copyright (c) 2019, Verizon and Calix.   All rights reserved.";

  revision "2020-10-04" {
    description
      "Initial revision";
    reference
      "ITU-T Y.1731-2015 clause 7; MEF 7.2 clause 7.5.";
  }

  feature ecfm-y1731-fm {
    description
      "Indicates support for ITU-T Y.1731 Fault Management (FM).";
  }

  /* Augment maintenance associations with Y.1731-specific nodes. */
  augment "/vz-oam-ecfm:cfm/vz-oam-ecfm:domains/vz-oam-ecfm:domain"
        + "/vz-oam-ecfm:associations/vz-oam-ecfm:association" {
    description
      "Add configuration data nodes for Maintenance Entity Groups 
       (MEG) to associations.";

    leaf y1731-compliant {
      if-feature "ecfm-y1731-fm";
      type boolean;
      must ".='false' or "
         + "(.='true' and boolean(../../../vz-oam-ecfm:md-name/vz-oam-ecfm:no-name) and "
         + "boolean (../level))" {
        error-message
          "A ITU-T Y.1731 compliant maintenance association requires 
           the 'name-format' of the maintenance domain to be 
           configured to 'no-name' and a value for 'level' to be 
           configured at the association.";
        description
          "The maintenance domain name format must be set to 
           'no-name' and a level is required for the maintenance 
           association, if the maintenance association is to be 
           Y.1731 compliant.";
      }
      description
        "To identify whether this maintenance association
         represents an IEEE 802.1ag compliant MA (false) or
         an ITU-T Y.1731 compliant MEG (true).
         If false:
         - the MAID is provisioned in the CCM frames from the MD name
          (md-name-format, md-name) and MA Short Name
          (ma-name-format, ma-name)
         - MD Level is provisioned in the CCM frames from
          /domains/domain/level.
         If true:
         - the Maintenance Domain Name in CCM frames is null as
          required by Y.1731, i.e., MD Name Format in the CCM frame
          is set to none(1)
         - the MEGID is provisioned in the CCM frames based on
          ma-name-format and ma-name-format
         - ME Level (MEL) is provisioned in the CCM frames from level
          configured for the maintenance association.
         To configure a 802.1ag compatible CCM MAID field format,
         where the Maintenance Domain is not present, set
         ma-name-format to the Short MA Name Format and ma-name
         to the Short MA Name.";
    }

    leaf level {
      when "../y1731-compliant='true'" {
        description
          "Only valid and applicable when Y.1731 is enabled.";
      }
      if-feature "ecfm-y1731-fm";
      type uint8 {
        range "0..7";
      }
      description
        "The level associated with the MEG.";
    }
  }

  augment "/vz-oam-ecfm:cfm/vz-oam-ecfm:domains/vz-oam-ecfm:domain"
        + "/vz-oam-ecfm:associations/vz-oam-ecfm:association"
        + "/vz-oam-ecfm:short-ma-name"
        + "/vz-oam-ecfm:which-short-ma-name-format" {
    description
      "Add ITU-T Y.1731 specific short MA name formats.";

    case icc-based {
      container icc-based {
        description
          "ICC-based MEG_ID format";
        leaf icc {
          type string;
          description
            "ITU Carrier Code (ICC).";
          reference
            "ITU-T Y.1731 clause A.1.";
        }
        leaf umc {
          type string;
          description
            "Unique MEG ID code (UMC).";
          reference
            "ITU-T Y.1731 clause A.1.";
        }
        reference
          "ITU-T Y.1731 clause A.1.";
      }
    }
    case cc-and-icc-based {
      container cc-and-icc-based {
        description
          "Global MEG_ID format based on CC and ICC.";

        leaf cc {
          type string;
          description
            "Country Code (CC).";
          reference
            "ITU-T Y.1731 clause A.2.";
        }
        leaf icc {
          type string;
          description
            "ITU Carrier Code (ICC).";
          reference
            "ITU-T Y.1731 clause A.2.";
        }
        leaf umc {
          type string;
          description
            "Unique MEG ID code (UMC).";
          reference
            "ITU-T Y.1731 clause A.2.";
        }
        reference
          "ITU-T Y.1731 clause A.2.";
      }
    }
  }


  deviation "/vz-oam-ecfm:cfm/vz-oam-ecfm:domains/vz-oam-ecfm:domain"
          + "/vz-oam-ecfm:associations/vz-oam-ecfm:association" {
    description
      "The 'short-ma-name' may only appear once in the list of 
       associations. To include the additional short name formats 
       augmented above, additional unique statements can only be 
       added to the list 'association' through a deviation.";
    deviate add {
      unique "vz-oam-ecfm:short-ma-name/"
           + "vz-oam-ecfm:which-short-ma-name-format/icc-based/"
           + "icc-based/icc vz-oam-ecfm:short-ma-name/"
           + "vz-oam-ecfm:which-short-ma-name-format/icc-based/"
           + "icc-based/umc";
      unique "vz-oam-ecfm:short-ma-name/"
           + "vz-oam-ecfm:which-short-ma-name-format/"
           + "cc-and-icc-based/cc-and-icc-based/"
           + "cc vz-oam-ecfm:short-ma-name/"
           + "vz-oam-ecfm:which-short-ma-name-format/"
           + "cc-and-icc-based/cc-and-icc-based/"
           + "icc vz-oam-ecfm:short-ma-name/"
           + "vz-oam-ecfm:which-short-ma-name-format/"
           + "cc-and-icc-based/cc-and-icc-based/umc";
    }
  }

  /*
  augment "/vz-oam-ecfm:cfm-state/vz-oam-ecfm:domains/" 
    + "vz-oam-ecfm:domain/vz-oam-ecfm:associations/"
    + "vz-oam-ecfm:association" {
    description 
      "Add operational status nodes for Maintenance Entity Groups 
      (MEG) to associations.";


  }
   */
}
