submodule verizon-oam-ethernet-cfm-pm-lm {
  belongs-to verizon-oam-ethernet-cfm-pm {
    prefix vz-oam-ecfm-pm;
  }

  import verizon-oam-ethernet-cfm {
    prefix vz-oam-ecfm;
  }

  include verizon-oam-ethernet-cfm-pm-types;
  include verizon-oam-ethernet-cfm-pm-tca;
  include verizon-oam-ethernet-cfm-pm-base;
  include verizon-oam-ethernet-cfm-pm-lm-body;

  organization
    "Verizon";

  contact
    "Comments or questions about this Verizon YANG module should be
     directed to <mailto:vz-open-netconf-yang@verizon.com>";

  description
    "This module contains a collection of YANG definitions that
     extend the functionality of Connectivity Fault Management
     (CFM) as specified in IEEE 802.1ag with additional
     functionality to support the Ethernet Frame Loss Measurement
     (ETH-LM) function of Ethernet Service Layer OAM Performance 
     Monitoring as specified by ITU-T Y.1731 clause 8.1, MEF 35.1 
     and the management information models specified in MEF 7.2 
     clause 7.6.

     Copyright (c) 2019, Verizon and Calix.   All rights reserved.";

  revision "2020-10-04" {
    description
      "Initial revision";
    reference
      "ITU-T Y.1731-2015 clause 8.1; MEF 35.1; MEF 7.2 clause 7.6.";
  }


  feature reset-loss-measurement-statistics {
    description
      "Indicate support for the RPCs to reset loss measurement 
       statistics.";
  }

  typedef loss-measurement-tca-profile-ref {
    type leafref {
      path "/vz-oam-ecfm:cfm/vz-oam-ecfm-pm:profiles"
         + "/vz-oam-ecfm-pm:loss-measurement"
         + "/vz-oam-ecfm-pm:tca-profiles/vz-oam-ecfm-pm:tca-profile"
         + "/vz-oam-ecfm-pm:name";
    }
    description
      "A reference to an entry in the tca-profile list for loss 
       measurements.";
  }

  grouping loss-measurement-profiles {
    description
      "Defines the profiles for loss measurements.

       Editor's note: This leaf should preferably be included in the 
       grouping 'loss-measurement-session-config-parameters', 
       but this would cause a circular dependency when using the 
       current submodule structure as the typedef 
       'loss-measurement-bins-profile-ref' needed for this leaf is 
       defined within this module.
       For the long-term, the profile definitions could be extracted 
       out into their own submodules.";

    leaf tca-profile {
      if-feature "tca-reporting";
      type loss-measurement-tca-profile-ref;
      description
        "A reference to a loss measurement TCA profile. If no 
         profile is referenced, TCA reporting will be disabled 
         for the session.";
    }
  }

  /* Augment CFM profile configuration with TCA profiles for 
   *  ETH-LM. 
   */
  augment "/vz-oam-ecfm:cfm/vz-oam-ecfm-pm:profiles" {
    description
      "Add configuration nodes for loss measurement profiles.";

    container loss-measurement {
      description
        "Configuration of profiles for loss measurements.";

      container tca-profiles {
        if-feature "tca-reporting";
        description
          "Configuration of TCA profiles.";

        list tca-profile {
          key "name";
          description
            "A profiles for threshold crossing alert (TCA) 
             reporting.";

          leaf name {
            type string;
            description
              "A unique name for the profile.";
          }

          list stateless-tca {
            if-feature "stateless-tca-reporting";
            key "metric threshold";
            description
              "A stateless TCA configuration. Each configured 
               'stateless-tca' results in a TCA function within 
               a measurement session.";

            uses loss-measurement-stateless-tca-profile-parameters;
          }

          list stateful-tca {
            if-feature "stateful-tca-reporting";
            key "metric set-threshold";
            description
              "A stateful TCA configuration. Each configured 
               'stateful-tca' results in a TCA function within 
               a measurement session.";

            uses loss-measurement-stateful-tca-profile-parameters;
          }
        }
      }
    }
  }

  /* Augment MEP configuration with ETH-LM specific nodes. */
  augment "/vz-oam-ecfm:cfm/vz-oam-ecfm:domains/vz-oam-ecfm:domain"
        + "/vz-oam-ecfm:associations/vz-oam-ecfm:association"
        + "/vz-oam-ecfm:meps/vz-oam-ecfm:mep" {
    description
      "Add configuration nodes for the PM configuration for the
       Ethernet Loss Measurement (ETH-LM) function at a MEP.";

    container loss-measurement {
      if-feature "eth-lm";
      description
        "Configuration of the ETH-LM/ETH-SLM function at a MEP.";

      uses loss-measurement-config-parameters;

      container sessions {
        if-feature "proactive-sessions";
        description
          "Configuration of ETH-LM/ETH-SLM sessions.
           Only proactive sessions can be configured.";

        list session {
          key "name";
          description
            "Configuration of ETH-LM/ETH-SLM proactive sessions. ";

          leaf name {
            type string;
            description
              "The name of the proactive ETH-LM/ETH-SLM session at 
               the local MEP.";
          }
          uses common-proactive-session-config-parameters;
          uses loss-measurement-session-config-parameters;
          uses loss-measurement-profiles;
        }
      }
    }
  }

  /* Augment MEP operational status with ETH-DM specific nodes. */
  augment "/vz-oam-ecfm:cfm-state/vz-oam-ecfm:domains"
        + "/vz-oam-ecfm:domain/vz-oam-ecfm:associations"
        + "/vz-oam-ecfm:association/vz-oam-ecfm:meps"
        + "/vz-oam-ecfm:mep" {
    description
      "Add operational status of the ETH-LM/ETH-SLM function at a 
       MEP.";

    container loss-measurement {
      if-feature "eth-lm";
      description
        "Operational status of the ETH-LM/ETH-SLM function at a MEP.";

      uses loss-measurement-config-parameters;

      container sessions {
        description
          "Operational status of ETH-LM/ETH-SLM sessions.";

        list session {
          key "name session-type";
          description
            "The operational status of a ETH-LM/ETH-SLM session. 
             Any existing session will be automatically deleted by 
             the system, if the local MEP is deleted.

             Note that this list lists the operational status of both 
             proactive sessions, which are created per configuration 
             only, and on-demand sessions, which are created by RPC 
             call only, with the consequence that the session type 
             is implicit dependent on how the session is created.
             Since configuration data cannot reference state data, it 
             would not be possible to validate a configuration to 
             ensure the a session name used for on-demand sessions 
             is not configured for use as a proactive session.
             Therefore, in state data the additional leaf 
             'session-type' is used together with the 'name' of the 
             session as the key to the list, with the result that 
             the value of 'name' needs only to be unique within the 
             scope of 'session-type', i.e., identical names may be 
             used for both proactive and on-demand sessions.";

          leaf name {
            type string;
            description
              "The name of the ETH-LM/ETH-SLM session at the local 
               MEP.";
          }

          uses loss-measurement-session-status-parameters;
          uses loss-measurement-profiles;
        }
      }
    }
  }

  /* Augment MEP statistics with ETH-LM/ETH-SLM statistics */
  augment "/vz-oam-ecfm:cfm-state/vz-oam-ecfm:domains"
        + "/vz-oam-ecfm:domain/vz-oam-ecfm:associations"
        + "/vz-oam-ecfm:association/vz-oam-ecfm:meps/vz-oam-ecfm:mep"
        + "/vz-oam-ecfm:statistics" {
    description
      "Add operational status nodes for ETH-LM/ETH-SLM statistics.";

    container loss-measurement {
      if-feature "eth-lm";
      description
        "Operational status of ETH-LM/ETH-SLM statistics.";
    }
  }

  rpc create-on-demand-loss-measurement {
    if-feature "eth-lm";
    if-feature "on-demand-sessions";
    description
      "Create an on-demand ETH-LM/ETH-SLM session at a given MEP. 
       This will result in a corresponding entry in the 'session' 
       list for the given MEP in operational status only.
       Note that on-demand sessions must be started and stopped 
       explicitly through invocation of the 
       'start-on-demand-delay-measurement'  and 
       'stop-on-demand-delay-measurement' RPCs respectively.";
    reference
      "MEF 35.1 clause 10.1.3.";

    input {
      uses create-on-demand-loss-measurement-input-parameters;
      uses loss-measurement-profiles;
    }
    output {
      uses create-on-demand-loss-measurement-output-parameters;
    }
  }

  rpc start-on-demand-loss-measurement {
    if-feature "eth-lm";
    if-feature "on-demand-sessions";
    description
      "Start an on-demand ETH-LM/ETH-SLM session that has been 
       previously configured at the given MEP.
       If the session is already active, the measurements within the 
       current measurement interval will be restarted.";
    reference
      "MEF 35.1 clause 10.1.5.";

    input {
      uses start-on-demand-loss-measurement-input-parameters;
    }
    output {
      uses start-on-demand-loss-measurement-output-parameters;
    }
  }

  rpc stop-on-demand-loss-measurement {
    if-feature "eth-lm";
    if-feature "on-demand-sessions";
    description
      "Stop an on-demand ETH-LM/ETH-SLM session that has been 
       previously configured at the given MEP.
       If the session is already idle, the measurements the RPC will 
       have no effect.";
    reference
      "MEF 35.1 clause 10.1.5.";

    input {
      uses stop-on-demand-loss-measurement-input-parameters;
    }
    output {
      uses stop-on-demand-loss-measurement-output-parameters;
    }
  }

  rpc delete-on-demand-loss-measurement {
    if-feature "eth-lm";
    if-feature "on-demand-sessions";
    description
      "Delete an on-demand ETH-LM/ETH-SLM session that has been 
       previously created at the given MEP.";
    reference
      "MEF 35.1 clause 10.1.4.";

    input {
      uses delete-on-demand-loss-measurement-input-parameters;
    }
    output {
      uses delete-on-demand-loss-measurement-output-parameters;
    }
  }

  rpc reset-loss-measurement-statistics {
    if-feature "eth-lm";
    if-feature "reset-loss-measurement-statistics";
    description
      "Reset the measurement statistics for a ETH-LM/ETH-SLM
       session.";
    reference
      "MEF 7.2 clause 7.6.4.2 (reset()).";

    input {
      uses vz-oam-ecfm-pm:session-identification-parameters;
    }
  }

  rpc reset-loss-measurement-availability-statistics {
    if-feature "eth-lm";
    if-feature "reset-loss-measurement-statistics";
    description
      "Reset the availability statistics for a ETH-LM/ETH-SLM 
       session.";
    reference
      "MEF 7.2 clause 7.6.4.3 (reset()).";

    input {
      uses vz-oam-ecfm-pm:session-identification-parameters;
    }
  }
}
