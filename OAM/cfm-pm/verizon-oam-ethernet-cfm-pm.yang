module verizon-oam-ethernet-cfm-pm {

  namespace "http://www.verizon.com/ns/bbf-oam-ethernet-cfm-pm";
  prefix vz-oam-ecfm-pm;

  include verizon-oam-ethernet-cfm-pm-types;

  include verizon-oam-ethernet-cfm-pm-base;

  include verizon-oam-ethernet-cfm-pm-tca;

  include verizon-oam-ethernet-cfm-pm-lm;
  include verizon-oam-ethernet-cfm-pm-lm-body;

  include verizon-oam-ethernet-cfm-pm-dm;
  include verizon-oam-ethernet-cfm-pm-dm-body;

  organization
    "Verizon";

  contact
    "Comments or questions about this Verizon YANG module should be
     directed to <mailto:vz-open-netconf-yang@verizon.com>";

  description
    "This module contains a collection of YANG definitions for
     the management of Ethernet Service Layer OAM Performance
     Monitoring as specified by ITU-T Y.1731 clause 8, MEF 35.1 and 
     the management information models specified in MEF 7.2 clause 
     7.6 and augments those specified in the YANG module 
     'bbf-oam-ethernet-cfm', which implements support for 
     Connectivity Fault Management (CFM) as specified in 
     IEEE 802.1ag.

     Copyright (c) 2019, Verizon and Calix.   All rights reserved.";

  revision "2020-10-04" {
    description
      "Initial revision";
    reference
      "ITU-T Y.1731-2015 clause 8; MEF 35.1; MEF 7.2 clause 7.6.";
  }
}
