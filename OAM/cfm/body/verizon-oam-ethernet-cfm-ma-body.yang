submodule verizon-oam-ethernet-cfm-ma-body {
  belongs-to verizon-oam-ethernet-cfm {
    prefix vz-oam-ecfm;
  }
  include verizon-oam-ethernet-cfm-types;

  organization
    "Verizon";

  contact
    "Comments or questions about this Verizon YANG module should be
     directed to <mailto:vz-open-netconf-yang@verizon.com>";

  description
    "This module contains a collection YANG data types and grouping 
     definitions for the management of Maintenance Associations (MA) 
     within Connectivity Fault Management (CFM) as specified in 
     IEEE 802.1ag.

     Copyright (c) 2019, Verizon and Calix.   All rights reserved.";

  revision "2020-10-04" {
    description
      "Initial revision";
    reference "None";
  }

  grouping association-identification-parameters {
    description
      "Parameters required to uniquely identity a maintenance 
       association.";
    reference
      "IEEE 802.ag clause 12.14.7.1.2:a";
    leaf domain-admin-name {
      type admin-name;
      mandatory true;
      description
        "The admin-name of the domain in which the MEP is located.";
    }
    leaf association-admin-name {
      type admin-name;
      mandatory true;
      description
        "The admin-name of the association in which the MEP is 
         located.";
    }
  }


  grouping maintenance-association-name {
    description
      "Parameters used to determine the name of the string given
       a name format.";

    choice which-short-ma-name-format {
      description
        "The choice to select the name of the maintenance association 
         based on the required format.";
      reference
        "IEEE 802.1ag clause 12.14.5.3.2:b.";

      case primary-vid {
        leaf primary-vid {
          type empty;
          description
            "The name of the association is that of its primary VID.";
          reference
            "IEEE 802.1ag Table 21-20 (Value 1).";
        }
      }
      case character-string {
        leaf character-string {
          type string;
          description
            "The name of the association expressed as a character
             string.";
          reference
            "IEEE 802.1ag Table 21-20 (Value 2).";
        }
      }
      case uint16 {
        leaf uint16 {
          type uint16;
          description
            "The name of the association is a 2 octet integer.";
          reference
            "IEEE 802.1ag Table 21-20 (Value 3).";
        }
      }
      case rfc2685-vpn-id {
        container rfc2685-vpn-id {
          description
            "The name of the association is a 2 octet integer.";
          leaf vpn-oui {
            type uint32;
            description
              "VPN authority Organizationally Unique Identifier.";
            reference
              "RPC 2865.";
          }
          leaf vpn-index {
            type uint32;
            description
              "VPN index identifying the VPN according to the OUI.";
            reference
              "RPC 2865.";
          }
          reference
            "IEEE 802.1ag Table 21-20 (Value 4).";
        }
      }
    }
  }

  grouping maintenance-association-config-parameters {
    description
      "Parameters associated with a Maintenance Association (MA).";

    container short-ma-name {
      description
        "The short Maintenance Association (MA) Name that is unique 
         within the Maintenance Domain, where the Maintenance Domain 
         Name and the Short MA Name form the Maintenance Association 
         Identifier (MAID) that is carried in CFM PDUs to identify 
         inadvertent connections among MEPs.";
      uses maintenance-association-name {
        refine "which-short-ma-name-format" {
          mandatory true;
        }
      }
    }

    container mep-list {
      description
        "A list of all the MEPIDs that belong to this MA. 
         From this list, a local MEP can determine its peer or 
         remote MEPs.
         This list needs to be configured, if auto-discovery of 
         peer MEPs is not supported by a device or reliance on 
         auto-discovery is not desired.";
      reference
        "IEEE 802.1ag clause 12.14.6.1.3:g";
      leaf-list mep-id {
        type mep-id;
        description
          "A MEPID that belongs to this MA. ";
        reference
          "IEEE 802.1ag clause 12.14.6.1.3:g";
      }
    }
  }
}
