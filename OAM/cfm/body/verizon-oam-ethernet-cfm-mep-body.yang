submodule verizon-oam-ethernet-cfm-mep-body {
  belongs-to verizon-oam-ethernet-cfm {
    prefix vz-oam-ecfm;
  }

  include verizon-oam-ethernet-cfm-types;
  include verizon-oam-ethernet-cfm-ma-body;
  include verizon-oam-ethernet-cfm-mp-body;

  organization
    "Verizon";

  contact
    "Comments or questions about this Verizon YANG module should be
     directed to <mailto:vz-open-netconf-yang@verizon.com>";
  
  description
    "This module contains a collection YANG data types and grouping 
     definitions for the management of Maintenance Association End 
     Points (MEP) within Connectivity Fault Management (CFM) as 
     specified in IEEE 802.1ag.

     Copyright (c) 2019, Verizon and Calix.   All rights reserved.";

  revision "2020-10-04" {
    description
      "Initial revision";
    reference "None";
  }


  grouping frame-destination {
    description
      "Defines the parameters needed to configure a destination of 
       an OAM frame.";
    choice destination-address-type {
      description
        "This choice determines the how the destination is 
         to be defined.";
      case mep-id {
        leaf mep-id {
          type mep-id;
          description
            "The MEPID of another MEP in the same Maintenance 
             Association to which the a message is to be sent.

             NOTE: 
             The MEPID must be present as an entry in the 
             remote-mep-database of the MEP which is to send 
             the message.";
        }
      }
      case mac-address {
        leaf mac-address {
          type string {
            pattern 
              '[0-9a-fA-F]{1}[02468aAcCeE]{1}(:[0-9a-fA-F]{2}){5}' {
              description
                "Match on the standard MAC address format of
                 xx:xx:xx:xx:xx:xx allowing both upper and lowercase
                 letters but disallow any address with bit 0 in the
                 first octet being set to a 1 which represents a
                 multicast address";
            }
          }
          must ". != '00:00:00:00:00:00'" {
            description
              "Disallow a MAC address of 00:00:00:00:00:00";
          }
          description
            "The unicast MAC address of the maintenance entity.";
        }
      }
    }
  }

  grouping frame-target {
    description
      "Defines the parameters needed to configure a target of 
       an OAM frame.";
    choice target-address-type {
      description
        "This choice determines the how the target is to be 
         defined.";
      case mep-id {
        leaf mep-id {
          type mep-id;
          description
            "The MEPID of another MEP in the same maintenance 
             association / MEG to which the a message is to be sent.

             NOTE: 
             The MEPID must be present as an entry in the 
             remote-mep-database of the MEP which is to send 
             the message.";
        }
      }
      case mac-address {
        leaf mac-address {
          type string {
            pattern 
              '[0-9a-fA-F]{1}[02468aAcCeE]{1}(:[0-9a-fA-F]{2}){5}' {
              description
                "Match on the standard MAC address format of
                 xx:xx:xx:xx:xx:xx allowing both upper and lowercase
                 letters but disallow any address with bit 0 in the
                 first octet being set to a 1 which represents a
                 multicast address";
            }
          }
          must ". != '00:00:00:00:00:00'" {
            description
              "Disallow a MAC address of 00:00:00:00:00:00";
          }
          description
            "The unicast mac-address of the maintenance entity.";
        }
      }
    }
  }

  grouping mep-identification-parameters {
    description
      "Parameters required to uniquely identity a MEP.";
    reference
      "IEEE 802.ag clause 12.14.7.1.2:a";

    uses association-identification-parameters;

    leaf mep-id {
      type mep-id;
      mandatory true;
      description
        "The MEPID of the MEP to be identified.";
      reference
        "IEEE 802.ag clause 12.14.6.3.2:b";
    }
  }

  grouping mep-config-parameters {
    description
      "Configuration parameters associated with a MEP.";

    uses mp-config-parameters {
      refine "enabled" {
        description
          "If true, indicates the MEP is enabled and can function
           normally.  If false, the MEP is to cease functioning.";
        reference
          "IEEE 802.1ag clauses 12.14.7.1.3:e and 20.9.1";
      }
    }

    leaf direction {
      type enumeration {
        enum "down" {
          description
            "Sends CFM PDUs away from the MAC Relay Entity.";
        }
        enum "up" {
          description
            "Sends CFM PDUs towards the MAC Relay Entity.";
        }
      }
      mandatory true;
      description
        "The direction the MEP is facing";
      reference
        "IEEE 802.1ag clauses 12.14.7.1.3:c and 19.2";
    }

    leaf ccm-ltm-priority {
      type frame-priority;
      mandatory true;
      description
        "The priority value for CCMs and LTMs transmitted 
         by the MEP.";
      reference
        "IEEE 802.1ag clause 12.14.7.1.3:h";
    }
  }

  grouping mep-status-parameters {
    description
      "Status parameters associated with a MEP.";

    uses mp-status-parameters {
      refine "mac-address" {
        description
          "The MAC address associated with the MEP.";
        reference
          "IEEE 802.1ag clause 12.14.7.1.3:i and 19.4";
      }
      refine "oper-status" {
        description
          "The operational status of the MEP";
      }
    }
  }
}
