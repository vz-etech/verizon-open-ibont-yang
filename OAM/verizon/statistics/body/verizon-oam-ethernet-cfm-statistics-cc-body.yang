submodule verizon-oam-ethernet-cfm-statistics-cc-body {
  belongs-to verizon-oam-ethernet-cfm-statistics {
    prefix vz-oam-ecfm-stats;
  }
  
  import ietf-yang-types {
    prefix yang;
  }

  organization 
    "Verizon";

  contact
    "Comments or questions about this Verizon YANG module should be
     directed to <mailto:vz-open-netconf-yang@verizon.com>";

  description 
    "This module contains a collection YANG data types and grouping 
     definitions to support continuity check statistics that are not 
     defined as part of the standards IEEE 802.1ag, ITU-T Y.1731 or 
     MEF 7.2.

     Copyright (c) 2019, Verizon and Calix.   All rights reserved.";

  revision "2020-10-04" {
    description
      "Initial revision";
    reference "None";
  }

  grouping continuity-check-statistics-parameters {
    description
      "Statistics parameters for the continuity check 
       protocol of a MEP.";

    leaf in-ccm-rdi {
      type yang:counter64;
      description
        "The total number of Continuity Check (CCM) messages 
         received by the MEP in which the RDI flag was set.";
    }
    leaf out-ccm-rdi {
      type yang:counter64;
      description
        "The total number of Continuity Check (CCM) messages 
         transmitted by the MEP in which the RDI flag was set.";
    }
    leaf in-ccm-sender-id-invalid {
      type yang:counter64;
      description
        "The total number of Continuity Check (CCM) messages 
         received by the MEP in which the Sender ID was invalid.";
    }
    leaf in-ccm-port-status-invalid {
      type yang:counter64;
      description
        "The total number of Continuity Check (CCM) messages 
         received by the MEP in which the Port Status was invalid.";
    }
    leaf in-ccm-if-status-invalid {
      type yang:counter64;
      description
        "The total number of Continuity Check (CCM) messages 
         received by the MEP in which the Interface Status was 
         invalid.";
    }
  }
  
}
