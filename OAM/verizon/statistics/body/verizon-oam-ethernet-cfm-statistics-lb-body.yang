submodule verizon-oam-ethernet-cfm-statistics-lb-body {
  belongs-to verizon-oam-ethernet-cfm-statistics {
    prefix vz-oam-ecfm-stats;
  }
  
  import ietf-yang-types {
    prefix yang;
  }
  
  organization 
    "Verizon";

  contact
    "Comments or questions about this Verizon YANG module should be
     directed to <mailto:vz-open-netconf-yang@verizon.com>";
 
  description 
    "This module contains a collection YANG data types and grouping 
     definitions to support loopback statistics that are not defined 
     as part of the standards IEEE 802.1ag, ITU-T Y.1731 or 
     MEF 7.2.

     Copyright (c) 2019, Verizon and Calix.   All rights reserved.";

  revision "2020-10-04" {
    description
      "Initial revision";
    reference "None";
  }


  grouping loopback-statistics-parameters {
    description
      "Statistics parameters for the loopback protocol of a MEP.";

    leaf out-lbm {
      type yang:counter64;
      description
        "The total number of LBMs transmitted by the MEP.";
    }
  }
  
}
