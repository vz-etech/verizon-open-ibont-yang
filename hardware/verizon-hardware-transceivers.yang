module verizon-hardware-transceivers {
  namespace "http://www.verizon.com/ns/verizon-hardware-transceivers";
  prefix vz-hw-xvr;

  import verizon-hardware {
    prefix vz-hw;
  }
  
  import verizon-notifications {
    prefix vz-nfc;
  }

  organization
    "Verizon";

  contact
    "Comments or questions about this Verizon YANG module should be
     directed to <mailto:vz-open-netconf-yang@verizon.com>";

  description
    "This module contains a collection of YANG definitions for
     managing transceivers.

     Copyright (c) 2019, Verizon and Calix.   All rights reserved.";

  revision "2020-10-04" {
    description
      "Initial revision";
    reference "None";
  }
  
  // Hardware Component  
  identity transceiver {
    base vz-hw:module;
    description
      "This identity is applicable if the hardware class is some 
       pluggable or non-pluggable transceiver, e.g. SFP.";
  }
  

  // Event Identities
  identity transceiver-event-identity {
    base vz-nfc:event-identity;
    description
      "Base identity for all transceiver event identities.";
  }
  
  identity transceiver-inserted {
    base transceiver-event-identity;
    description
      "A transceiver has been inserted.";
  }
  
  identity transceiver-removed {
    base transceiver-event-identity;
    description
      "A transceiver has been removed.";
  }
  

  // Alarm Identities
  identity transceiver-alarm-identity {
    base vz-nfc:alarm-identity;
    description
      "Base identity for all transceiver alarm identities.";
  }
  
  identity transceiver-failure {
    base transceiver-alarm-identity;
    description
      "Failed to read the inserted transceiver.";
  }


  // Alarm/warning flags
  identity alarm-warning {
    description
      "Base identity for the alarm and warning flags of the
       transceiver.";
  }
  
  identity transceiver-alarm-warning {
    base alarm-warning;
    description
      "Base identity for the basic alarm and warning flags of the
       transceiver.";
  }
  
  identity temperature-high {
    base transceiver-alarm-warning;
    description
      "Present when internal temperature has exceeded the 
       high level threshold.";
  }
  
  identity temperature-low {
    base transceiver-alarm-warning;
    description
      "Present when internal temperature has dropped below the 
       low level threshold.";
  }
  
  identity supply-voltage-high {
    base transceiver-alarm-warning;
    description
      "Present when internal supply voltage has exceeded the 
       high level threshold.";
  }
  
  identity supply-voltage-low {
    base transceiver-alarm-warning;
    description
      "Present when internal supply voltage has dropped below 
       the low level threshold.";
  }
  
  identity link-alarm-warning {
    base alarm-warning;
    description
      "Base identity for the physical links of alarm and warning flags
       of the transceiver.";
  }

  identity tx-bias-high {
    base link-alarm-warning;
    description
      "Present when TX bias current has exceeded the high 
       level threshold.";
  }
  
  identity tx-bias-low {
    base link-alarm-warning;
    description
      "Present when TX bias current has dropped below the low 
       level threshold.";
  }
  
  identity tx-power-high {
    base link-alarm-warning;
    description
      "Present when TX output power has exceeded the high 
       level threshold.";
  }
  
  identity tx-power-low {
    base link-alarm-warning;
    description
      "Present when TX output power has dropped below the low 
       level threshold.";
  }
  
  identity rx-power-high {
    base link-alarm-warning;
    description
      "Present when RX output power has exceeded the high 
       level threshold.";
  }
  
  identity rx-power-low {
    base link-alarm-warning;
    description
      "Present when RX output power has dropped below the low 
       level threshold.";
  }
  
  identity laser-temperature-high {
    base link-alarm-warning;
    description
      "Present when laser temperature has exceeded the high 
       level threshold.";
  }
  
  identity laser-temperature-low {
    base link-alarm-warning;
    description
      "Present when laser temperature has dropped below the low 
       level threshold.";
  }
  
  identity tec-current-high {
    base link-alarm-warning;
    description
      "Present when TEC current has exceeded the high level 
       threshold.";
  }
  
  identity tec-current-low {
    base link-alarm-warning;
    description
      "Present when TEC current has dropped below the low level 
       threshold.";
  }


  //Physical Device Identifiers
  identity physical-device {
    description
      "Identifies the physical device.";
    reference
      "SFF-8472 Version 12.2, Section 5.1 - Physical Device 
       Identifier Values";
  }
  
  identity unknown-physical-device {
    base physical-device;
    description
      "Unknown or unspecified.";
    reference
      "SFF-8472 Version 12.2, Table 5-1, Value 00h";
  }
  
  identity gbic {
    base physical-device;
    description
      "Gigabit Interface Converter.";
    reference
      "SFF-8472 Version 12.2, Table 5-1, Value 01h";
  }
  
  identity sff {
    base physical-device;
    description
      "Small form-factor module soldered to a motherboard.";
    reference
      "SFF-8472 Version 12.2, Table 5-1, Value 02h";
  }
  
  identity sfp-or-sfp-plus {
    base physical-device;
    description
      "Small form-factor pluggable or small form-factor pluggable 
       plus.";
    reference
      "SFF-8472 Version 12.2, Table 5-1, Value 03h";
  }



  grouping vendor-parameters {
    description
      "Management objects related to the vendor of the transceiver.";
  
    leaf name {
      type string {
        length "0..16";
      }
      description
        "The vendor name shall be the full name of the corporation, 
         a commonly accepted abbreviation of the name of the 
         corporation, the SCSI company code for the corporation, 
         or the stock exchange code for the corporation.";
      reference
        "SFF-8472 Version 12.2, Section 7.1 - Vendor name";
    }
    
    leaf part-number {
      type string {
        length "0..16";
      }
      description
        "The vendor part number (vendor PN) is an up to 16-byte 
         field that defines the vendor part number or product name. 
         A empty string indicates that the vendor PN is 
         unspecified.";
      reference
        "SFF-8472 Version 12.2, Section 7.3 - Vendor PN";
    }
    
    leaf revision {
      type string {
        length "0..4";
      }
      description
        "The vendor revision number that defines the Vendor's 
         product revision number. An empty string indicates that the 
         vendor revision is unspecified.";
      reference
        "SFF-8472 Version 12.2, Section 7.4 - Vendor Rev";
    }
    
    leaf serial-number {
      type string {
        length "0..16";
      }
      description
        "The vendor serial number that defines the Vendor's serial 
         number for the transceiver. An empty string indicates that 
         the vendor SN is unspecified.";
      reference 
        "SFF-8472 Version 12.2, Section 8.6 - Vendor SN"; 
    }
    
    leaf date-code {
      type string {
        length "8"; 
        pattern '[0-9]{4}\-[0-9]{2}\-[0-9]{2}';
      }
      description
        "The date code contains the Vendor's date code. The date 
         code is mandatory.";
      reference
        "SFF-8472 Version 12.2, Section 8.7 - Data Code"; 
    }
  }
  

  
  grouping link-parameters {
    description
      "Management objects related to the physical link of the
       transceiver.";
    
    leaf wavelength {
      type uint32;
      units "nm";
      description
        "The laser wavelength in nanometers.";
      reference
        "SFF-8472 Version 12.2, Section 8 - Link Characteristics";
    }
  }    
  
  
  /* Diagnostics */
  grouping transceiver-diagnostic-parameters {
    description
      "Management objects related to retrieving diagnostic
       data from the transceiver.";
      
    leaf diagnostics-valid {
      type boolean;
      description
        "If true, the transceiver supports digital
         diagnostic monitoring and the available data is valid.";
      reference
        "SFF-8472 Version 12.2, Section 8.8 - Diagnostic 
         Monitoring Type";
    }
    
    leaf temperature {
      type decimal64 {
        fraction-digits 3;
        range "-128.000..128.000";
      }
      units "degrees Celsius";
      description
        "Internally measured transceiver temperature Temperature 
         accuracy is vendor specific but must be better than +/- 3 
         degrees Celsius over specified operating temperature and 
         voltage. ";
      reference 
        "SFF-8472 Version 12.2, Section 9 - Diagnostics";
    }
    
    leaf supply-voltage {
      type decimal64 {
        fraction-digits 4;
        range "0..6.5535";
      }
      units "volts";
      description
        "Internally measured transceiver supply voltage. Practical 
         considerations to be defined by transceiver manufacturer 
         will tend to limit the actual bounds of the supply voltage 
         measurement. Accuracy is vendor specific but must be better 
         than +/- 3% of the manufacturer's nominal value over 
         specified operating temperature and voltage. Note that in 
         some transceivers, transmitter supply voltage and receiver 
         supply voltage are isolated. In that case, only one supply 
         is monitored. Refer to the device specification for more 
         detail."; 
      reference 
        "SFF-8472 Version 12.2, Section 9 - Diagnostics";
    }
  }
  
  grouping link-diagnostic-parameters {
    description
      "Management objects related to retrieving diagnostic physical 
       link data from the transceiver.";
    
    leaf tx-bias {
      type decimal64 {
        fraction-digits 3;
        range "0..131.070";
      }
      units "mA";
      description
        "Measured TX bias current in mA. Accuracy is vendor specific 
         but must be better than +/- 10% of the manufacturer's 
         nominal value over specified operating temperature and 
         voltage.";   
      reference 
        "SFF-8472 Version 12.2, Section 9 - Diagnostics";
    }
    
    leaf tx-power {
      type decimal64 {
        fraction-digits 4;
        range "0..6.5535";
      }
      units "mW";
      description
        "Measured TX output power in mW. Data is assumed to be based 
         on measurement of laser monitor photodiode current. It is 
         factory calibrated to absolute units using the most 
         representative fiber output type. Accuracy is vendor 
         specific but must be better than +/- 3dB over specified 
         temperature and voltage. Data is not valid when the 
         transmitter is disabled."; 
      reference 
        "SFF-8472 Version 12.2, Section 9 - Diagnostics";
    }
          
    leaf rx-power {
      type decimal64 {
        fraction-digits 4;
        range "0..6.5535";
      }
      units "mW";
      description
        "Measured RX received optical power in mW. Absolute accuracy 
         is dependent upon the exact optical wavelength. For the 
         vendor specified wavelength, accuracy shall be better than 
         +/- 3dB over specified temperature and voltage. This 
         accuracy shall be maintained for input power levels up to 
         the lesser of maximum transmitted or maximum received 
         optical power per the appropriate standard. It shall be 
         maintained down to the minimum transmitted power minus cable 
         plant loss (insertion loss or passive loss) per the 
         appropriate standard. Absolute accuracy beyond this minimum 
         required received input optical power range is vendor 
         specific."; 
      reference 
        "SFF-8472 Version 12.2, Section 9 - Diagnostics";
    }
    
    leaf laser-temperature {
      type int32 {
        range "-128000..128000";
      }
      units "degrees Celsius";
      description
        "Measured optional laser temperature. The relative and 
         absolute accuracy are vendor specific but relative laser 
         temperature accuracy must be better than +/- 0.2 degrees 
         Celsius. [Relative temperature accuracy refers to the 
         accuracy of the reported temperature changes relative to the 
         actual laser temperature changes]."; 
      reference 
        "SFF-8472 Version 12.2, Section 9 - Diagnostics";
    }
    
    leaf tec-current {
      type int16;
      units "0.1mA";
      description
        "Measured TEC current. The format is signed two's complement 
         with the LSB equal to 0.1 mA. Thus a range from -3276.8 to 
         +3276.7 mA may be reported with a resolution of 0.1 mA. 
         Reported TEC current is a positive number for cooling and a 
         negative number for heating. The accuracy of the TEC current
         monitor is vendor specific but must be better than +/- 15% 
         of the maximum TEC current as stored in the TEC current high 
         alarm threshold.";
      reference 
        "SFF-8472 Version 12.2, Section 9 - Diagnostics";
    }
  }
  
  grouping transceiver-alarm-diagnostic-parameters {
    description
      "Management objects related to retrieving diagnostic basic 
       alarm data from the transceiver.";
    
    leaf-list alarm-flag {
      type identityref {
        base transceiver-alarm-warning;
      }
      
      description
        "Alarm flags associated with transceiver temperature and 
         supply voltage as well as reserved locations for future 
         flags. Alarm flags indicate conditions likely to be 
         associated with an in-operational link and cause for 
         immediate action.";
      reference 
        "SFF-8472 Version 12.2, Section 9.8 - Alarm and Warning
         Flag Bits.
         SFF-8436 Version 4.8, Section 7.6.1.6 - Module and Channel
         Masks.";
    }
    
    leaf-list warning-flag {
      type identityref {
        base transceiver-alarm-warning;
      }
      description
        "Warning flags associated with transceiver temperature and 
         supply voltage as well as reserved locations for 
         future flags. Warning flags indicate conditions outside the 
         normally guaranteed bounds but not necessarily causes of 
         immediate link failures. Certain warning flags may also be 
         defined by the manufacturer as end-of-life indicators (such 
         as for higher than expected bias currents in a constant 
         power control loop)."; 
      reference 
        "SFF-8472 Version 12.2, Section 9.8 - Alarm and Warning
         Flag Bits.
         SFF-8436 Version 4.8, Section 7.6.1.6 - Module and Channel
         Masks.";
    }
  }
  
  grouping link-alarm-diagnostic-parameters {
    description
      "Management objects related to retrieving diagnostic physical 
       link alarm data from the transceiver.";
    
    leaf-list alarm-flag {
      type identityref {
        base link-alarm-warning;
      }
      
      description
        "Alarm flags associated with transceiver TX bias current,
         TX output power and received optical power as well as
         reserved locations for future flags. Alarm flags indicate 
         conditions likely to be associated with an in-operational
         link and cause for immediate action.";
      reference 
        "SFF-8472 Version 12.2, Section 9.8 - Alarm and Warning
         Flag Bits.
         SFF-8436 Version 4.8, Section 7.6.1.6 - Module and Channel
         Masks.";
    }
    
    leaf-list warning-flag {
      type identityref {
        base link-alarm-warning;
      }
      description
        "Warning flags associated with TX bias current, TX output
         power and received optical power as well as reserved 
         locations for future flags. Warning flags indicate conditions
         outside the normally guaranteed bounds but not necessarily 
         causes of immediate link failures. Certain warning flags may
         also be defined by the manufacturer as end-of-life indicators
         (such as for higher than expected bias currents in a constant
         power control loop)."; 
      reference 
        "SFF-8472 Version 12.2, Section 9.8 - Alarm and Warning
         Flag Bits.
         SFF-8436 Version 4.8, Section 7.6.1.6 - Module and Channel
         Masks.";
    }
  }
  
  grouping transceiver-compliance-codes {
    description
      "Nodes which allow reporting of the transceivers compliance.";
    
    container compliance-codes {
      description
        "Compliance codes which collectively represent the electronic
         or optical interfaces that are supported by the 
         transceiver.";
      reference
        "SFF-8472 Version 12.2, Section 5.4 - Transceiver Compliance
         Codes.";
         
      leaf ten-gigabit-ethernet {
        type enumeration {
          enum not-applicable {
            description
              "Not applicable.";
          }
          enum ten-gig-base-er {
            description
              "10G Base-ER [A0=3, bit 7]";
          }
          enum ten-gig-base-lrm {
            description
              "10G Base-LRM [A0=3, bit 6]";
          }
          enum ten-gig-base-lr {
            description
              "10G Base-LR [A0=3, bit 5]";
          }
          enum ten-gig-base-sr {
            description
              "10G Base-SR [A0=3, bit 4]";
          }
        }
        default "not-applicable";
        description
          "10G Ethernet Compliance Codes.";
      }
         
      leaf infiniband {
        type enumeration {
          enum not-applicable {
            description
              "Not applicable.";
          }
          enum inf-1x-sx {
            description
              "1X SX [A0=3, bit 3]";
          }
          enum inf-1x-lx {
            description
              "1X LX [A0=3, bit 2]";
          }
          enum inf-1x-cu-act {
            description
              "1X Copper Active [A0=3, bit 1]";
          }
          enum inf-1x-cu-pass {
            description
              "1X Copper Passive [A0=3, bit 0]";
          }
        }
        default "not-applicable";
        description
          "Infiniband Compliance Codes.";
      }
      
      leaf ethernet {
        type enumeration {
          enum not-applicable {
            description
              "Not applicable.";
          }
          enum eth-base-px {
            description
              "BASE-PX [A0=6, bit 7]";
          }
          enum eth-base-bx10 {
            description
              "BASE-BX10 [A0=6, bit 6]";
          }
          enum eth-100base-fx {
            description
              "100BASE-FX [A0=6, bit 5]";
          }
          enum eth-100base-lx {
            description
              "100BASE-LX/LX-10 [A0=6, bit 4]";
          }
          enum eth-1000base-t {
            description
              "100BASE-T [A0=6, bit 3]";
          }
          enum eth-1000base-cx {
            description
              "1000BASE-CX [A0=6, bit 2]";
          }
          enum eth-1000base-lx {
            description
              "1000BASE-LX [A0=6, bit 1]";
          }
          enum eth-1000base-sx {
            description
              "1000BASE-SX [A0=6, bit 0]";
          }
        }
        default "not-applicable";
        description
          "Ethernet Compliance Codes.";
      }
        
      
      leaf fibre-channel-link-length {
        type enumeration {
          enum not-applicable {
            description
              "Not applicable.";
          }
          enum v {
            description
              "Very long distance (V) [A0=7, bit 7]";
          }
          enum s {
            description
              "Short distance (S) [A0=7, bit 6]";
          }
          enum i {
            description
              "Intermediate distance (I) [A0=7, bit 5]";
          }
          enum l {
            description
              "Long distance (L) [A0=7, bit 4]";
          }
          enum m {
            description
              "Medium distance (M) [A0=7, bit 3]";
          }
        }
        default "not-applicable";
        description
          "Fibre channel link length.";
      }
      
      leaf fiber-channel-technology {
        type enumeration {
          enum not-applicable {
            description
              "Not applicable.";
          }
          enum sa {
            description
              "Shortwave laser, linear (SA) [A0=7, bit 2]";
          }
          enum lc {
            description
              "Longwave laser (LC) [A0=7, bit 1]";
          }
          enum el-inter {
            description
              "Electrical inter-enclosure (EL) [A0=7, bit 0]";
          }
          enum el-intra {
            description
              "Electrical intra-enclosure (EL) [A0=8, bit 7]";
          }
          enum sn {
            description
              "Shortwave laser w/o OFC (SN) [A0=8, bit 6]";
          }
          enum sl {
            description
              "Shortwave laser with OFC (SL) [A0=8, bit 5]";
          }
          enum ll {
            description
              "Longwave laser (LL) [A0=8, bit 4]";
          }
        }
        default "not-applicable";
        description
          "Fibre channel technology.";
      }
      
      leaf sfp-plus-cable-technology {
        type enumeration {
          enum not-applicable {
            description
              "Not applicable.";
          }
          enum active {
            description
              "Active Cable [A0=8, bit 3]";
          }
          enum passive {
            description
              "Passive Cable [A0=8, bit 2]";
          }
        }
        default "not-applicable";
        description
          "SFP+ cable technology.";
      }
      
      leaf fibre-channel-transmission-media {
        type bits {
          bit tw {
            description
              "Twin Axial Pair (TW) [A0=9, bit 7]";
          }
          bit tp {
            description
              "Twin Twisted Pair (TP) [A0=9, bit 6]";
          }
          bit mi {
            description
              "Miniature Coax (MI) [A0=9, bit 5]";
          }
          bit tv {
            description
              "Video Coax (TV) [A0=9, bit 4]";
          }
          bit m6 {
            description
              "Multimode, 62.5um (M6) [A0=9, bit 3]";
          }
          bit m5 {
            description
              "Multimode, 50um (M5 or M5E) [A0=9, bit 2]";
          }
          bit sm {
            description
              "Single Mode (SM) [A0=9, bit 0]";
          }
        }
        default "";
        description
          "Fibre channel transmission media.";
      }
      
      leaf fibre-channel-speed {
        type bits {
          bit mbs-1200 {
            description 
              "1200 MBytes/sec [A0=10, bit 7]";
          }
          bit mbs-800 {
            description 
              "800 MBytes/sec [A0=10, bit 6]";
          }
          bit mbs-1600 {
            description 
              "1600 MBytes/sec [A0=10, bit 5]";
          }
          bit mbs-400 {
            description 
              "400 MBytes/sec [A0=10, bit 4]";
          }
          bit mbs-3200 {
            description 
              "3200 MBytes/sec [A0=10, bit 3]";
          }
          bit mbs-200 {
            description 
              "200 MBytes/sec [A0=10, bit 2]";
          }
          bit mbs-100 {
            description 
              "100 MBytes/sec [A0=10, bit 0]";
          }
        }
        default "";
        description
          "Fibre channel speed.";
      }
    }
  }
  
  augment "/vz-hw:hardware-state/vz-hw:component" {
    description
      "Augment the hardware state with transceiver specific data.";
    
    container transceiver {
      when "../vz-hw:class='vz-hw-xvr:transceiver'" {
        description
          "These data nodes are only applicable when the component
           is a transceiver.";
      }
      description
        "State data associated with a transceiver.";

      leaf physical-device {
        type identityref {
          base physical-device;
        }
        description
          "Identifies the physical device.";
        reference
          "SFF-8472 Version 12.2, Section 5.1 - Physical Device 
           Identifier Values";
      }
      
      uses transceiver-compliance-codes;
      
      container vendor {
        description
          "Management objects related to the vendor of the 
           transceiver.";
          
        uses vendor-parameters;
      }
      
      container links {
        description
          "Physical link data of the transceiver. For 
           example, SFPs and XSFPs can be have only one physical 
           link, but QSFPs can be have up to 4 physical links.";
        
        leaf maximum-link-length {
          type uint32;
          units "meters";
          description
            "The maximum link length currently supported by the
             transceiver.";
          reference 
            "SFF-8472 Version 12.2, Section 6 - Link Length";
        }
        
        list link {
          key number;
          max-elements 1;
          description
            "A physical link on the transceiver.";

          
          leaf number {
            type uint32 {
              range "1";
            }
            description
              "Unique number to identifier a physical link. The
               number corresponds to the register entry of the
               physical link in the transceiver.";
          }
          
          uses link-parameters;
        }
      }
      
      container diagnostics {
        description
          "Diagnostic data of the transceiver.";
        
        uses transceiver-diagnostic-parameters;
        
        uses transceiver-alarm-diagnostic-parameters;
      
        list link {
          key number;
          description
            "Physical link data of the transceiver. For example, SFPs
             and XSFPs can be have only one physical link, but QSFPs
             can be have up to 4 physical links.";
          
          leaf number {
            type uint32;
            description
              "Unique number to identifier a physical link. The
               number corresponds to the register entry of the
               physical link in the transceiver.";
          }
          
          uses link-diagnostic-parameters;
          
          uses link-alarm-diagnostic-parameters;
        }
      }
    }
  }
}
