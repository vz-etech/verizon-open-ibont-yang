module verizon-hardware {
  namespace "http://www.verizon.com/ns/verizon-hardware";
  prefix vz-hw;

  import ietf-yang-types {
    prefix yang;
  }

  organization
    "Verizon";

  contact
    "Comments or questions about this Verizon YANG module should be
     directed to <mailto:vz-open-netconf-yang@verizon.com>" ;

  description
    "This module contains a collection of YANG definitions for
     managing hardware.  This module is derived from early IETF 
     Hardware YANG model.

     Copyright (c) 2019, Verizon and Calix.   All rights reserved.
     
     Copyright (c) 2017 IETF Trust and the persons identified as
     authors of the code.  All rights reserved.";

  revision "2020-10-04" {
    description
      "Initial revision";
    reference "None";
  }
 
  identity hardware-class {
    description
      "This identity is the base for all hardware class
       identifiers.";
  }

  identity unknown {
    base hardware-class;
    description
      "This identity is applicable if the hardware class is unknown
       to the server.";
  }

  identity chassis {
    base hardware-class;
    description
      "This identity is applicable if the hardware class is an
       overall container for networking equipment.  Any class of
       physical component, except a stack, may be contained within a
       chassis; a chassis may only be contained within a stack.";
  }

  identity container {
    base hardware-class;
    description
      "This identity is applicable if the hardware class is capable
       of containing one or more removable physical entities,
       possibly of different types.  For example, each (empty or
       full) slot in a chassis will be modeled as a container.  Note
       that all removable physical components should be modeled
       within a container component, such as field-replaceable
       modules, fans, or power supplies.  Note that all known
       containers should be modeled by the agent, including empty
       containers.";
  }

  identity module {
    base hardware-class;
    description
      "This identity is applicable if the hardware class is some sort
       of self-contained sub-system.  If a module component is
       removable, then it should be modeled within a container
       component; otherwise, it should be modeled directly within
       another physical component (e.g., a chassis or another
       module).";
  }
  
  typedef hardware-component-state-ref {
    type leafref {
      path "/vz-hw:hardware-state/vz-hw:component/vz-hw:name";
    }
    description
      "Used to reference a hardware component in the state list.";
  }
 
  container hardware-state {
    config false;
    description
      "Data nodes for the operational state of components.";

    leaf last-change {
      type yang:date-and-time;
      description
        "The time the '/hardware-state/component' list changed.";
    }

    list component {
      key name;
      description
        "List of components.

         When the server detects a new hardware component, it
         initializes an entry in this list.

         If the server does not support the feature
         'hardware-config', the entry is initialized with values for
         all nodes as detected by the implementation.

         Otherwise, the following procedure is followed:

           1. If there is an entry in the /hardware/component list
              with values for the nodes 'class', 'parent',
              'parent-rel-pos' that are equal to the detected values,
              then:

           1a. If the configured entry has a value for 'mfg-name'
               that is equal to the detected value, or if the
               'mfg-name' value cannot be detected, then the entry is
               initialized with the configured values for all
               configured leafs, including the 'name'.

               Otherwise, the entry is initialized with values for
               all nodes as detected by the implementation.  The
               implementation may raise an alarm that informs about
               the 'mfg-name' mismatch condition.  How this is done
               is outside the scope of this document.

           1b. Otherwise (i.e., there is no matching configuration
               entry), the entry is initialized with values for all
               nodes as detected by the implementation.

         If the /hardware/component list is modified (i.e., someone
         changed the configuration), then the system MUST behave as
         if it re-initializes itself, and follow the procedure in
         (1).";

      reference "RFC 6933: entPhysicalEntry";

      leaf name {
        type string;
        description
          "The name assigned to this component.

           This name is not required to be the same as
           entPhysicalName.";
      }

      leaf class {
        type identityref {
          base hardware-class;
        }
        mandatory true;
        description
          "An indication of the general hardware type of the
           component.";
        reference "RFC 6933: entPhysicalClass";
      }

      leaf description {
        type string;
        description
          "A textual description of component.  This node should
           contain a string that identifies the manufacturer's name
           for the component and should be set to a distinct value
           for each version or model of the component.";
        reference "RFC 6933: entPhysicalDescr";
      }

      leaf parent {
        type leafref {
          path "../../component/name";
        }
        description
          "The name of the component that physically contains this
           component.

           If this leaf is not instantiated, it indicates that this
           component is not contained in any other component.

           In the event that a physical component is contained by
           more than one physical component (e.g., double-wide
           modules), this node contains the name of one of these
           components.  An implementation MUST use the same name
           every time this node is instantiated.";
        reference "RFC 6933: entPhysicalContainedIn";
      }

      leaf parent-rel-pos {
        type int32 {
          range "0 .. 2147483647";
        }
        description
          "An indication of the relative position of this child
           component among all its sibling components.  Sibling
           components are defined as components that share the same
           instance values of each of the 'parent' and 'class'
           nodes.";
        reference "RFC 6933: entPhysicalParentRelPos";
      }

      leaf-list contains-child {
        type leafref {
          path "../../component/name";
        }
        description
          "The name of the contained component.";
        reference "RFC 6933: entPhysicalChildIndex";
      }

      leaf hardware-rev {
        type string;
        description
          "The vendor-specific hardware revision string for the
           component.  The preferred value is the hardware revision
           identifier actually printed on the component itself (if
           present).";
        reference "RFC 6933: entPhysicalHardwareRev";
      }

      leaf firmware-rev {
        type string;
        description
          "The vendor-specific firmware revision string for the
           component.";
        reference "RFC 6933: entPhysicalFirmwareRev";
      }

      leaf software-rev {
        type string;
        description
          "The vendor-specific software revision string for the
           component.";
        reference "RFC 6933: entPhysicalSoftwareRev";
      }

      leaf serial-num {
        type string;
        description
          "The vendor-specific serial number string for the
           component.  The preferred value is the serial number
           string actually printed on the component itself (if
           present).

           If a serial number has been configured for this component
           in /hardware/component/serial-num, this node contains the
           configured value.";
        reference "RFC 6933: entPhysicalSerialNum";
      }

      leaf mfg-name {
        type string;
        description
          "The name of the manufacturer of this physical component.
           The preferred value is the manufacturer name string
           actually printed on the component itself (if present).

           Note that comparisons between instances of the model-name,
           firmware-rev, software-rev, and the serial-num nodes are
           only meaningful amongst component with the same value of
           mfg-name.

           If the manufacturer name string associated with the
           physical component is unknown to the server, then this
           node is not instantiated.";
        reference "RFC 6933: entPhysicalMfgName";
      }

      leaf model-name {
        type string;
        description
          "The vendor-specific model name identifier string
           associated with this physical component.  The preferred
           value is the customer-visible part number, which may be
           printed on the component itself.

           If the model name string associated with the physical
           component is unknown to the server, then this node is not
           instantiated.";
        reference "RFC 6933: entPhysicalModelName";
      }

      leaf alias {
        type string;
        description
          "An 'alias' name for the component, as specified by a
           network manager, and provides a non-volatile 'handle' for
           the component.

           If an alias has been configured for this component in
           /hardware/component/alias, this node contains the
           configured value.  If no such alias has been configured,
           the server may set the value of this node to a locally
           unique value.";
        reference "RFC 6933: entPhysicalAlias";
      }

      leaf asset-id {
        type string;
        description
          "This node is a user-assigned asset tracking identifier for
           the component.

           If an asset tracking identifier has been configured for
           this component in /hardware/component/asset-id, this node
           contains the configured value.";
        reference "RFC 6933: entPhysicalAssetID";
      }

      leaf is-fru {
        type boolean;
        description
          "This node indicates whether or not this component is
           considered a 'field replaceable unit' by the vendor.  If
           this node contains the value 'true', then this component
           identifies a field replaceable unit.  For all components
           that are permanently contained within a field replaceable
           unit, the value 'false' should be returned for this
           node.";
        reference "RFC 6933: entPhysicalIsFRU";
      }

      leaf mfg-date {
        type yang:date-and-time;
        description
          "The date of manufacturing of the managed component.";
        reference "RFC 6933: entPhysicalMfgDate";
      }

    }
  }
}
