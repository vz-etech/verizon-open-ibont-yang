submodule verizon-ipfix-exporter {
  belongs-to verizon-ipfix {
    prefix vz-ipfix;
  }

  import ietf-inet-types {
    prefix inet;
  }
  
  import ietf-yang-types {
    prefix yang;
  }

  include verizon-ipfix-base;

  organization
    "Verizon";
    
  contact
    "Comments or questions about this Verizon YANG module should be
     directed to <mailto:vz-open-netconf-yang@verizon.com>";
     
  description
    "This module contains IPFIX exporter and collector YANG model
     in support of Verizon IPFIX.

     Copyright (c) 2019, Verizon and Calix.   All rights reserved.";
  
revision "2020-10-04" {
    description
      "Initial revision";
    reference "None";
  }

  /*
   * Identities
   */

  identity export-mode {
    description
      "Base identity for different usages of export
       destinations configured for an Exporting Process.";
  }

  identity parallel {
    base export-mode;
    description
      "Parallel export of Data Records to all
       destinations configured for the Exporting Process.";
  }

  identity load-balancing {
    base export-mode;
    description
      "Load-balancing between the different destinations
       configured for the Exporting Process.";
  }

  identity fallback {
    base export-mode;
    description
      "Export to the primary destination (i.e., the first
       SCTP, UDP, TCP, or file destination configured for the
       Exporting Process).  If the export to the primary destination
       fails, the Exporting Process tries to export to the secondary
       destination.  If the secondary destination fails as well, it
       continues with the tertiary, etc.";
  }

  identity options-type {
    description
      "Base identity for report types exported with
       options templates.";
  }

  identity metering-statistics {
    base options-type;
    description
      "Metering Process Statistics.";
    reference
      "RFC 5101, Section 4.1.";
  }

  identity metering-reliability {
    base options-type;
    description
      "Metering Process Reliability Statistics.";
    reference
      "RFC 5101, Section 4.2.";
  }

  identity exporting-reliability {
    base options-type;
    description
      "Exporting Process Reliability
       Statistics.";
    reference
      "RFC 5101, Section 4.3.";
  }

  identity flow-keys {
    base options-type;
    description
      "Flow Keys.";
    reference
      "RFC 5101, Section 4.4.";
  }

  identity selection-sequence {
    base options-type;
    description
      "Selection Sequence and Selector Reports.";
    reference
      "RFC 5476, Sections 6.5.1 and 6.5.2.";
  }

  identity selection-statistics {
    base options-type;
    description
      "Selection Sequence Statistics Report.";
    reference
      "RFC 5476, Sections 6.5.3.";
  }

  identity accuracy {
    base options-type;
    description
      "Accuracy Report.";
    reference
      "RFC 5476, Section 6.5.4.";
  }

  identity reducing-redundancy {
    base options-type;
    description
      "Enables the utilization of Options Templates to
       reduce redundancy in the exported Data Records.";
    reference
      "RFC 5473.";
  }

  identity extended-type-information {
    base options-type;
    description
      "Export of extended type information for
       enterprise-specific Information Elements used in the
       exported Templates.";
    reference
      "RFC 5610.";
  }


  /*
   * Groupings
   */

  // Export Configuration Groupings
  grouping exporting-process-parameters {
    description
      "Parameters of an Exporting Process.";
    leaf export-mode {
      type identityref {
        base export-mode;
      }
      default 'parallel';
      description
        "This parameter determines to which configured
         destination(s) the incoming Data Records are exported.";
    }
    list destination {
      key "name";
      min-elements 1;
      description
        "List of export destinations.";
      leaf name {
        type name-type;
        description "Key of this list.";
      }
      choice destination-parameters {
        mandatory true;
        description
          "Configuration parameters depend on whether
           SCTP, UDP, or TCP is used as transport protocol, and
           whether the destination is a file.";
        container sctp-exporter {
          if-feature sctp-transport;
          description "SCTP parameters.";
          uses sctp-exporter-parameters;
        }
        container udp-exporter {
          if-feature udp-transport;
          description "UDP parameters.";
          uses udp-exporter-parameters;
        }
        container tcp-exporter {
          if-feature tcp-transport;
          description "TCP parameters.";
          uses tcp-exporter-parameters;
        }
        container file-writer {
          if-feature file-writer;
          description
            "File Writer parameters.";
          uses file-writer-parameters;
        }
      }
    }

    list options {
      key "name";
      description
        "List of options reported by the Exporting
         Process.";
      leaf name {
        type name-type;
        description "Key of this list.";
      }
      uses options-parameters;
    }
  }

  grouping common-exporter-parameters {
    description
      "Parameters of en export destination that are
       common to all transport protocols.";
    leaf ipfix-version {
      type uint16;
      default '10';
      description "IPFIX version number.";
      reference
         "RFC 5101.";
    }
    leaf destination-port {
      type inet:port-number;
      description
        "If not configured by the user, the Monitoring
         Device uses the default port number for IPFIX, which is
         4739 without TLS or DTLS and 4740 if TLS or DTLS is
         activated.";
    }
/* This IETF choice statement is being commented out.
BBF has not yet fully worked out the ONT if-interfaces
names and rather that having to configure which interface
host is going to be used for ipfix export, a source-method
has been added that permits the device to choose which method
to use (e.g, either an explicit ip-address or derive it based
on some other logic).  If additional choices are needed, the
source-method choice statement
can be augmented to.

    choice index-or-name {
      description
        "Index or name of the interface as stored in the
         ifTable of IF-MIB.
         If configured, the Exporting Process MUST use the given
         interface to export IPFIX Messages to the export
         destination.
         If omitted, the Exporting Process selects the outgoing
         interface based on local routing decision and accepts
         return traffic, such as transport-layer acknowledgments,
         on all available interfaces.";
      reference
         "RFC 2863.";
      leaf if-index {
         type uint32;
         description
           "Index of an interface as stored in the ifTable of
            IF-MIB.";
         reference
           "RFC 2863.";
      }
      leaf if-name {
         type string;
         description
           "Name of an interface as stored in the ifTable of
            IF-MIB.";
         reference
           "RFC 2863.";
      }
    }
*/
    leaf send-buffer-size {
      type uint32;
      units "bytes";
      description
        "Size of the socket send buffer.
         If not configured by the user, this parameter is set by
         the Monitoring Device.";
    }
    leaf rate-limit {
      type uint32;
      units "bytes per second";
      description
        "Maximum number of bytes per second the Exporting
         Process may export to the given destination.  The number of
         bytes is calculated from the lengths of the IPFIX Messages
         exported.  If not configured, no rate limiting is
         performed.";
      reference
        "RFC 5476, Section 6.3.";
    }
    container transport-layer-security {
      presence
        "If transportLayerSecurity is present, DTLS is
         enabled if the transport protocol is SCTP or UDP, and TLS
         is enabled if the transport protocol is TCP.";
      description
        "TLS or DTLS configuration.";
      uses transport-layer-security-parameters;
    }
  }

  grouping sctp-exporter-parameters {
    description
      "SCTP-specific export destination parameters.";
    uses common-exporter-parameters;
    choice source-method {
      description
        "Method to configure the source IP address
         of the exporter.  Note that augmentations
         can be made to this choice statement for
         those additional methods.";
      case source-address {
        leaf-list source-address {
          type inet:ip-address;
          description
            "List of source IP addresses used by the
             Exporting Process.
             If configured, the specified addresses are eligible local
             IP addresses of the multihomed SCTP endpoint.
             If not configured, all locally assigned IP addresses are
             eligible local IP addresses.";
        reference
          "RFC 4960, Section 6.4.";
        }
      }
    }
    choice destination-method {
      description
        "Method to configure the destination IP address
         of the exporter.  Note that augmentations
         can be made to this choice statement for
         those additional methods.";
      case destination-address {
        leaf-list destination-ip-address {
          type inet:ip-address;
          min-elements 1;
        description
          "One or more IP addresses of the Collecting
           Process to which IPFIX Messages are sent.
           The user MUST ensure that all configured IP addresses
           belong to the same Collecting Process.
           The Exporting Process tries to establish an SCTP
           association to any of the configured destination IP
           addresses.";
        reference
          "RFC 4960, Section 6.4.";
        }
      }
    }
    leaf timed-reliability {
      type uint32;
      units "milliseconds";
      default '0';
      description
        "Lifetime in milliseconds until an IPFIX
         Message containing Data Sets only is 'abandoned' due to
         the timed reliability mechanism of PR-SCTP.
         If this parameter is set to zero, reliable SCTP
         transport is used for all Data Records.
         Regardless of the value of this parameter, the Exporting
         Process MAY use reliable SCTP transport for Data Sets
         associated with Options Templates.";
      reference
        "RFC 3758; RFC 4960.";
    }
  }

  grouping udp-exporter-parameters {
    description
      "Parameters of a UDP export destination.";
       uses common-exporter-parameters;
    choice source-method {
      description
        "Method to configure the source IP address
         of the exporter.  Note that it is expected
         that other methods be available.  Those
         method can augment this choice.";
      case source-address {
        leaf source-address {
          type inet:ip-address;
          description
            "Select Source-ip-address used
             by the Exporting Process. ";
        }
      }
    }
    choice destination-method {
      mandatory true;
      description
        "Method to configuring the IP address destination
         of the Collection Process to which IPFIX Messages are sent.
         Note it is expected that if other methods are available
         that they would augment from this statement.";
      case destination-address {
        leaf destination-address {
        type inet:host;
        description
          "Select ip-address or hostname.  A hostname may resolve
           to one or more IP-addresses.";
        }
      }
     }
    leaf max-packet-size {
      type uint16;
      units "octets";
      description
        "This parameter specifies the maximum size of
         IP packets sent to the Collector.  If set to zero, the
         Exporting Device MUST derive the maximum packet size
         from path MTU discovery mechanisms.
         If not configured by the user, this parameter is set by
         the Monitoring Device.";
    }
    leaf template-refresh-timeout {
      type uint32;
      units "seconds";
      default '600';
      description
        "Sets time after which Templates are resent in the
         UDP Transport Session.
         Note that the configured lifetime MUST be adapted to the
         templateLifeTime parameter value at the receiving Collecting
         Process.
         Note that this parameter corresponds to
         ipfixTransportSessionTemplateRefreshTimeout in the IPFIX
         MIB module.";
      reference
        "RFC 5101, Section 10.3.6; RFC 6615, Section 8
         (ipfixTransportSessionTemplateRefreshTimeout).";
    }
    leaf options-template-refresh-timeout {
      type uint32;
      units "seconds";
      default '600';
      description
        "Sets time after which Options Templates are
         resent in the UDP Transport Session.
         Note that the configured lifetime MUST be adapted to the
         optionsTemplateLifeTime parameter value at the receiving
         Collecting Process.
         Note that this parameter corresponds to
         ipfixTransportSessionOptionsTemplateRefreshTimeout in the
         IPFIX MIB module.";
      reference
        "RFC 5101, Section 10.3.6; RFC 6615, Section 8
         (ipfixTransportSessionOptionsTemplateRefreshTimeout).";
    }
    leaf template-refresh-packet {
      type uint32;
      units "IPFIX Messages";
      description
        "Sets number of IPFIX Messages after which
         Templates are resent in the UDP Transport Session.
         Note that this parameter corresponds to
         ipfixTransportSessionTemplateRefreshPacket in the IPFIX
         MIB module.
         If omitted, Templates are only resent after timeout.";
      reference
        "RFC 5101, Section 10.3.6; RFC 6615, Section 8
         (ipfixTransportSessionTemplateRefreshPacket).";
    }
    leaf options-template-refresh-packet {
      type uint32;
      units "IPFIX Messages";
      description
        "Sets number of IPFIX Messages after which
         Options Templates are resent in the UDP Transport Session
         protocol.
         Note that this parameter corresponds to
         ipfixTransportSessionOptionsTemplateRefreshPacket in the
         IPFIX MIB module.
         If omitted, Templates are only resent after timeout.";
      reference
        "RFC 5101, Section 10.3.6; RFC 6615, Section 8
        (ipfixTransportSessionOptionsTemplateRefreshPacket).";
      }
    }

  grouping tcp-exporter-parameters {
    description
      "Parameters of a TCP export destination.";
    uses common-exporter-parameters;
    choice source-method {
      description
        "Method to configure the source IP address
         of the exporter.  Note that it is expected
         that other methods be available.  Those
         method can augment this choice.";
      case source-address {
        leaf source-address {
          type inet:ip-address;
          description
            "Select Source-ip-address used
             by the Exporting Process.  ";
        }
      }
    }
    choice destination-method {
      mandatory true;
      description
        "Method to configuring the IP address destination
         of the Collection Process to which IPFIX Messages are sent.
         Note it is expected that if other methods are available
         that they would augment from this statement.";
      case destination-address {
        leaf destination-address {
        type inet:host;
        description
          "Select ip-address or hostname.  A hostname may resolve
           to one or more IP-addresses.";
        }
      }
    }
  }

  grouping file-writer-parameters {
    description "File Writer parameters.";
    leaf ipfix-version {
      type uint16;
      default '10';
      description "IPFIX version number.";
      reference
        "RFC 5101.";
    }
    leaf file {
      type inet:uri;
      mandatory true;
      description
        "URI specifying the location of the file.";
    }
  }

  grouping options-parameters {
    description
      "Parameters specifying the data export using an
       Options Template.";
    leaf options-type {
      type identityref {
        base options-type;
      }
      mandatory true;
      description
        "Type of the exported options data.";
    }

    leaf options-timeout {
      type uint32;
      units "milliseconds";
      description
        "Time interval for periodic export of the options
         data.  If set to zero, the export is triggered when the
         options data has changed.
         If not configured by the user, this parameter is set by the
         Monitoring Device.";
    }
  }

  // Export State Grouping
  grouping exporting-process-parameters-state {
    description
      "Parameters of an Exporting Process.";
    leaf export-mode {
      type identityref {
        base export-mode;
      }
      default 'parallel';
      description
        "This parameter determines to which configured
         destination(s) the incoming Data Records are exported.";
    }
  }

  grouping exporting-process-state-parameters {
    description
      "Describes the exporting process state top level grouping.";
    list destination {
      key "name";
      min-elements 1;
      description
        "List of export destinations.";
      leaf name {
        type name-type;
        description "Key of this list.";
      }
      choice destination-parameters {
        description
          "Retrieved session information depend on whether
           SCTP, UDP, or TCP is used as transport protocol, and
           whether the destination is a file.";
        container sctp-exporter-transporter-session {
          if-feature sctp-transport;
          description "SCTP session information.";
          uses transport-session-state-parameters;
        }
        container udp-exporter-transporter-session {
          if-feature udp-transport;
          description "UDP session information.";
          uses transport-session-state-parameters;
        }
        container tcp-exporter-transporter-session {
          if-feature tcp-transport;
          description "TCP session information.";
          uses transport-session-state-parameters;
        }
        container file-writer-transporter-session {
          if-feature file-writer;
          description
            "File Writer session information.";
          uses file-writer-parameters-state;
        }
      }
    }
  }

  grouping file-writer-parameters-state {
    description "File Writer state parameters.";
    leaf bytes {
      type yang:counter64;
      units "octets";
      description
        "The number of bytes written by the File Writer.
         Discontinuities in the value of this counter can occur at
         re-initialization of the management system, and at other
         times as indicated by the value of
         fileWriterDiscontinuityTime.";
    }
    leaf messages {
      type yang:counter64;
      units "IPFIX Messages";
      description
        "The number of IPFIX Messages written by the File
         Writer.
         Discontinuities in the value of this counter can occur at
         re-initialization of the management system, and at other
         times as indicated by the value of
         fileWriterDiscontinuityTime.";
    }
    leaf discarded-messages {
      type yang:counter64;
      units "IPFIX Messages";
      description
        "The number of IPFIX Messages that could not be
         written by the File Writer due to internal buffer
         overflows, limited storage capacity, etc.
         Discontinuities in the value of this counter can occur at
         re-initialization of the management system, and at other
         times as indicated by the value of
         fileWriterDiscontinuityTime.";
    }
    leaf records {
      type yang:counter64;
      units "Data Records";
      description
        "The number of Data Records written by the File Writer.
         Discontinuities in the value of this counter can occur at
         re-initialization of the management system, and at other
         times as indicated by the value of
         fileWriterDiscontinuityTime.";
    }
    leaf templates {
      type yang:counter32;
      units "Templates";
      description
        "The number of Template Records (excluding Options Template
         Records) written by the File Writer. Discontinuities in the
         value of this counter can occur at re-initialization of the
         management system, and at other times as indicated by the
         value of file-writer-discontinuity-time.";
    }
    leaf options-templates {
      type yang:counter32;
      units "Options Templates";
     description
       "The number of Options Template Records written by the File
        Writer. Discontinuities in the value of this counter can
        occur at re-initialization of the management system, and at
        other times as indicated by the value of
        file-writer-discontinuity-time.";
    }
    leaf file-writer-discontinuity-time {
      type yang:date-and-time;
      description
        "Timestamp of the most recent occasion at which one or more
         File Writer counters suffered a discontinuity. In contrast
         to discontinuity times in the IPFIX MIB module, the time is
         absolute and not relative to sysUpTime.";
    }
    list template {
      description
        "This list contains the Templates and Options Templates that
         have been written by the File Reader. Withdrawn or
         invalidated (Options) Templates MUST be removed from this
         list.";
      uses template-parameters-state;
    }
  }


  /*
   * Data Definitions
   */

  // IPFIX Exporter Configuration
  augment /vz-ipfix:ipfix {
    description "Augment ipfix container with exporter config data.";
    list exporting-process {
      if-feature exporter;
      key "name";
      description
        "List of Exporting Processes of the IPFIX Monitoring Device
         for which configuration will be applied.";
      leaf name {
        type name-type;
        description "Key of this list.";
      }
      uses exporting-process-parameters;
    }
  }

  // IPFIX Exporter State Data
  augment /vz-ipfix:ipfix-state {
    description
      "Augment ipfix state container with exporter state data.";
    list exporting-process {
      if-feature exporter;
      key "name";
      description
        "List of Exporting Processes of the IPFIX Monitoring Device
         for which state data will be retrieved.";
      leaf name {
        type leafref {
          path "/vz-ipfix:ipfix"
             + "/vz-ipfix:exporting-process"
             + "/vz-ipfix:name";
         }
        description "Key of this list.";
      }
      leaf exporting-process-id {
        type uint32;
        description
          "The identifier of the Exporting Process.
           This parameter corresponds to the Information Element
           exportingProcessId.  Its occurrence helps to associate
           Exporting Process parameters with Exporing Process
           statistics exported by the Monitoring Device using the
           Exporting Process Reliability Statistics Template as
           defined by the IPFIX protocol specification.";
      reference
        "RFC 5101, Section 4.3; IANA registry for IPFIX
         Entities, http://www.iana.org/assignments/ipfix.";
      }
      uses exporting-process-state-parameters;
    }
  }
}
