module verizon-ipfix-statistics {
  namespace "http://www.verizon.com/ns/verizon-ipfix-statistics";
  prefix vz-ipfix-stat;

  import verizon-ipfix {
    prefix vz-ipfix;
  }
  import ietf-yang-types {
    prefix yang;
  }

  organization
    "Verizon";

  contact
    "Comments or questions about this Verizon YANG module should be
     directed to <mailto:vz-open-netconf-yang@verizon.com>";

  description
    "This module describes IPFIX module to 
     configure statistics defined in netconf tree
     (e.g., if:interfaces-state/interface/statistics).
     and do not require the configuration of a meter.

     Copyright (c) 2019, Verizon and Calix.   All rights reserved.";

  revision "2020-10-04" {
    description
      "Initial revision";
    reference "None";
  }

  revision 2018-02-23 {
    description
      "Change module name from vz-ipfix-bulkstats to 
       verizon-ipfix-bulkstats.
       
       Change namespace to align with other Verizon models.

       Rename 'sampling-template' to 'statistics-template'.";
    reference 
      "TBD";
  }

  revision 2018-02-09 {
    description 
      "Updated revision date and prefix.";
    reference 
      "TBD";
  }
  
  revision 2018-02-05 {
    description 
      "2nd revision.  Changes:
        a) fixed tabing issue
        b) change submodule to module";
    reference 
      "TBD";
  }
  
  revision 2018-01-29 {
    description 
      "1st revision containing Calix-ADTRAN agreed upon principles.";
    reference 
      "TBD";
  }

  /*
   * Features
   */

  feature statistics {
    description
      "Statistics can be configured.";
  }

  /*
   * Types
   */

/* Place holder for future work on filtering
  grouping filterParameters {
    description "Configuration and state parameters of a Filter.";
    choice filter {
      leaf passthrough {
        type boolean;
      description "Is this a passthrough mode?.";
      }
    container ieid-match {
      description "Filter on the exact match";
    }
      container ieid-compare {
        description "ieid-compare.";
      }
    }
  }
 */

  /*
   * Groupings
   */

  grouping statistics-template-parameters {
    description "Statistics template parameters";
    leaf observation-domain-id {
      type uint32;
      default 0;
    description
      "An identifier of an Observation Domain that is locally unique
       to an Exporting Process (see RFC 7011 Section 3.1).
       Typically, this Information Element is
       for limiting the scope of other Information Elements.
       A value of 0 indicates that no specific Observation Domain is
       identified by this Information Element.";
    }
    container field-layout {
      description "Field Layout parameters.";
      list field {
        key name;
        min-elements 1;
        description
          "Superset of statistics field names or special
           field-names (e.g., timestamps, etc) for interpreting
           statistics that are included in the
           Packet Reports or Flow Records generated by the device.";
        leaf name {
          type vz-ipfix:name-type;
          description "Key of this list.";
        }
        choice identifier {
          mandatory true;
          description
            "ID of the Information Element to use in Packet Reports or
             Flow Records.";
          reference
            "RFC5102.";
          leaf ie-id {
            type vz-ipfix:ie-id-type;
            description
              "ID of the Information Element.";
          }
        }
        leaf ie-length {
          type uint16;
          units octets;
          description
            "Length of the field in which the Information
             Element is encoded.  A value of 65535 specifies a
             variable-length Information Element.  For Information
             Elements of integer and float type, the field length MAY
             be set to a smaller value than the standard length of
             the abstract data type if the rules of reduced size
             encoding are fulfilled.
             If not configured by the user, this parameter is set by
             the Monitoring Device.";
          reference "RFC 5101, Section 6.2.";
        }
        leaf ie-enterprise-number {
          type uint32;
          default 0;
          description
            "If this parameter is zero, the Information
             Element is registered in the IANA registry of IPFIX
             Information Elements or unspecified (if the 
             Informational Element is not IANA registered).
             If this parameter is configured with a non-zero private
             enterprise number, the Information Element is
             enterprise-specific.";
          reference
            "RFC 5101; RFC 5103;
             IANA registry for Private Enterprise Numbers,
             http://www.iana.org/assignments/enterprise-numbers
             IANA registry for IPFIX Entities,
             http://www.iana.org/assignments/ipfix.";
        }
      }
    }
  }

/* Place holder for future work on filtering
  list filtering-process {
    if-feature sampling-template;
    key name;
    description "Filtering Process of the Monitoring Device.";
    leaf name {
      type name-type;
      description "Key of this list.";
    }
    list filter {
      key name;
      min-elements 1;
      ordered-by user;
        description "List of Filters that define the action of the
        Selection Process on a single packet.  The Selectors are
        serially invoked in the same order as they appear in this
        list.";
      leaf name {
      type name-type;
      description "Key of this list.";
      }
      uses filterParameters;
    }
    leaf sampling-template {
      type leafref { path "/ipfix:ipfix/sampling-template/name"; }
      description "Cache that receives the output of the
      Selection Process.";
    }
  }
*/

  /*
   * Data definitions
   */

  augment '/vz-ipfix:ipfix' {
    description
      "Augment Verizon IPFIX to include the statistics templates.";

    list statistics-template {
      if-feature statistics;
        key name;
        description "Statistics template.";
        leaf name {
          type vz-ipfix:name-type;
          description "Key of this list.";
        }
      leaf export-interval {
        type uint32;
        units "seconds";
        description
          "This parameter configures the interval (in
           seconds) for periodical export of Flow Records.
           If not configured by the user, the Monitoring Device sets
           this parameter.";
      }
      uses statistics-template-parameters;
      leaf-list exporting-process {
        if-feature vz-ipfix:exporter;
        type leafref {
          path "/vz-ipfix:ipfix"
             + "/vz-ipfix:exporting-process"
             + "/vz-ipfix:name";
        }
        description
          "Records are exported by all Exporting Processes
           in the list.";
      }
    }
  }
  augment "/vz-ipfix:ipfix-state" {
    description
      "Augment Verizon IPFIX state to include statistics and status 
       related to statistics templates.";
       
    list statistics-template {
      if-feature statistics;
      key name;
      description "Statistics template of the Monitoring Device.";
      leaf name {
        type leafref {
          path "/vz-ipfix:ipfix/statistics-template/name";
        }
        description "Key of this list.";
      }
      leaf data-records {
        type yang:counter64;
        units "Data Records";
        description
          "The number of Data Records generated for this
           sampling template.  Discontinuities in the value of 
           this counter can occur at re-initialization of the
           management system, and at other times as indicated by 
           the value of Discontinuity Time.";
      }
      leaf discontinuity-time {
        type yang:date-and-time;
        description
          "Timestamp of the most recent occasion at which
           the counter data records suffered a discontinuity.";
      }
    }
  }
}
